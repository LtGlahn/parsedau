FME workspace lesdau_v_0_1.fmw

PythonCreator [off]
    NEW_ATTRIBUTES = feature_count
    PYTHONSOURCE:
      import fmeobjects
      import random

      # Template Class
      class FeatureCreator(object):
          def __init__(self):
              self.number = random.random()
          def close(self):
              for i in range(1, int(self.number*10)):

                  feature = fmeobjects.FMEFeature()
                  feature.setAttribute("feature_count", i)
                  self.pyoutput(feature)
    PYTHONSYMBOL = FeatureCreator
    -> PythonCreator_Output
PythonCreator_Output: Inspector
Creator
    GEOMTYPE = Geometry Object
    NUM = 1
    CREATED -> PythonCaller
PythonCaller
    NEW_ATTRIBUTES = feature_count
    PYTHONSOURCE:
      import fme
      import fmeobjects
      import random

      # Template Function interface:
      # def processFeature(feature):
      #    pass

      # Template Class Interface:
      class FeatureProcessor(object):
          def __init__(self):
              pass
          def input(self,feature):
              self.pyoutput(feature)
          def close(self):
              pass


      # Template Class
      class FeatureCreator(object):
          def __init__(self):
              self.number = random.random()

          def input(self, feature):
              pass
          def close(self):
              for i in range(1, int(self.number*10)):

                  feature = fmeobjects.FMEFeature()
                  feature.setAttribute("feature_count", i)
                  self.pyoutput(feature)
    PYTHONSYMBOL = FeatureCreator
    -> PythonCaller_Output
PythonCaller_Output: Inspector
